module p4-dtel-metadata-semantics {

  yang-version "1";

  // namespace value needs to be updated
  namespace "urn:p4:yang:p4-dtel-metadata-semantics";

  prefix "dtel-md";

  // import from openconfig or redefine locally?
  import openconfig-inet-types { prefix oc-inet; }

  // meta
  organization
    "P4.org Applications Working Group";

  contact
    "p4 apps working group p4-apps@lists.p4.org";

  description
    "Data model for nodes that support p4.org's dataplane telemetry
     specifications, primarily to report metadata semantics to
     telemetry monitoring systems.";

  revision "2018-07-03" {
    description "Initial version";
    reference
      "In-band Network Telemetry (INT) Dataplane Specification,
       Version 1.0, 2018-04-20;
       Telemetry Report Format Specification 1.0, 2018-04-20";
  }

  // identity statements

  identity METADATA_UNITS {
    description
      "Base identity for specifying units used to encode specific
       metadata";
  }

  identity METADATA_TIME_UNITS {
    base METADATA_UNITS;
    description
      "Base identity for specifying units of time";
  }

  identity METADATA_NANOSECONDS {
    base METADATA_TIME_UNITS;
    description
      "Encoding time in units of nanoseconds";
  }

  identity METADATA_FRACTIONAL_SECONDS {
    base METADATA_TIME_UNITS;
    description
      "Encoding time in units of 2^(-32) seconds";
  }

  identity METADATA_MICROSECONDS {
    base METADATA_TIME_UNITS;
    description
      "Encoding time in units of microseconds";
  }

  identity METADATA_SIZE_UNITS {
    base METADATA_UNITS;
    description
      "Base identity for specifying units of size, e.g. queue size";
  }

  identity METADATA_BYTES {
    base METADATA_SIZE_UNITS;
    description
      "Encoding size in units of bytes";
  }

  identity METADATA_CELLS {
    base METADATA_SIZE_UNITS;
    description
      "Encoding size in units of cells";
  }

  identity METADATA_PACKETS {
    base METADATA_SIZE_UNITS;
    description
      "Encoding size in units of packets";
  }

  identity METADATA_UTILIZATION_UNITS {
    base METADATA_UNITS;
    description
      "Base identity for specifying units of utilization";
  }

  identity METADATA_PERCENT {
    base METADATA_UTILIZATION_UNITS;
    description
      "Encoding utilization in units of percent";
  }

  identity METADATA_TENTHS_OF_PERCENT {
    base METADATA_UTILIZATION_UNITS;
    description
      "Encoding utilization in units of tenths of percent";
  }

  identity METADATA_HUNDREDTHS_OF_PERCENT {
    base METADATA_UTILIZATION_UNITS;
    description
      "Encoding utilization in units of hundredths of percent";
  }

  identity INTERFACE_TYPE {
    description
      "Base identity for specifying port types";
  }

  identity PHYSICAL_PORT {
    base INTERFACE_TYPE;
    description
      "Physical port on a switch";
  }

  identity FRONT_PANEL_PORT {
    base INTERFACE_TYPE;
    description
      "A number that indicates the front panel port and optionally channel
       on a switch";
  }

  identity LOGICAL_INTERFACE {
    base INTERFACE_TYPE;
    description
      "A logical interface on a switch";
  }

  identity L2_LOGICAL_INTERFACE {
    base INTERFACE_TYPE;
    description
      "An interface representing a VLAN or VNI on a switch";
  }

  identity VTEP_LOGICAL_INTERFACE {
    base INTERFACE_TYPE;
    description
      "An interface representing a VTEP on a switch";
  }

  // TODO: Add identity statements for L3 interfaces

  // typedef statements

  typedef queue-md-timing {
    type enumeration {
      enum ENQUEUE_TIME {
        description
          "Retrieval of metadata at packet enqueue time";
      }
      enum DEQUEUE_TIME {
        description
          "Retrieval of metadata at packet dequeue time";
      }
    }
    description
      "Specifies the timing of retrieval of queue related metadata";
  }

  typedef int-last-hop-md-report-position {
    type enumeration {
      enum EMBEDDED_INT {
        description
          "Last hop metadata is included with embedded INT metadata";
      }
      enum SAME_TELEMETRY_REPORT {
        description
          "Last hop metadata is included in the Telemetry Report
           header, in the same telemetry report as the embedded INT
           metadata from previous hops";
      }
      enum SEPARATE_TELEMETRY_REPORT {
        description
          "Last hop metadata is included in the Telemetry Report
           header, in a separate telemetry report from the embedded
           INT metadata from previous hops";
      }
    }
    description
      "Specifies whether last hop metadata is included in the same
       telemetry report as the embedded INT metadata from previous
       hops, and whether the last hop metadata is included in
       embedded INT metadata or in the Telemetry Report header";
  }

  // grouping statemenets

  grouping dtel-md-semantics-time-units {
    description
      "Units of time used for specific instances of INT metadata and
       telemetry report metadata";

    leaf time-units {
      type identityref {
        base METADATA_TIME_UNITS;
      }
      description
        "Units of time";
    }
  }

  grouping dtel-md-semantics-size-units {
    description
      "Units of size used for specific instances of INT metadata and
       telemetry report metadata";

    leaf size-units {
      type identityref {
        base METADATA_SIZE_UNITS;
      }
      description
        "Units of size";
    }

    leaf cell-size {
      when "../size-units = 'METADATA_CELLS'" {
        description
          "Cell size is valid only when the size is in units of
           cells";
      }
      type uint16;
      description
        "The size in bytes of one cell";
    }
  }

  grouping dtel-md-semantics-utilization-units {
    description
      "Units of utilization used for specific instances of INT
       metadata and telemetry report metadata";

    leaf utilization-units {
      type identityref {
        base METADATA_UTILIZATION_UNITS;
      }
      description
        "Units of utilization";
    }
  }

  grouping dtel-md-switch-id {
    description
      "Switch identifier used in dataplane telemetry metadata";

    leaf switch-id {
      type uint32;
      description
        "The switch_id value that this node inserts in INT metadata
         and telemetry report metadata";
    }

    leaf switch-id-mask {
      type uint32;
      description
        "The subset of the switch_id value that identifies the switch.
         The remainder of the switch_id value may be automatically
         assigned by the switch, or may be defined using yang
         augments.";
    }
  }

  grouping dtel-md-metadata-supported {
    description
      "Indicates whether a field is supported in INT metadata and
       telemetry report metadata";

    leaf supported-in-int {
      type boolean;
      description
        "Indicates whether a field is supported in INT metadata";
    }

    leaf supported-in-telemetry-reports {
      type boolean;
      description
        "Indicates whether a field is supported in telemetry report
         metadata";
    }
  }

  grouping dtel-md-level-1-interface {
    description
      "The list of interface types reported as level 1 interface IDs."

    uses dtel-md-interface-types;
    // TODO: define dtel-md-interface-types
  }

  grouping dtel-md-level-2-interface {
    description
      "The list of interface types reported as level 1 interface IDs."

    uses dtel-md-interface-types;
    // TODO: define dtel-md-interface-types
  }

  grouping dtel-md-hop-latency {
    description
      "Detailed semantics of hop latency in INT metadata and
       telemetry report metadata";

    uses dtel-md-semantics-time-units;
  }

  grouping dtel-md-queue-occupancy {
    description
      "Detailed semantics of queue occupancy in INT metadata and
       telemetry report metadata";

    uses dtel-md-semantics-size-units;

    leaf packet-timing {
      type queue-md-timing;
      description
        "Whether this queue occupancy was measured when the packet
         was enqueued, or when the packet was dequeued";
    }
  }

  grouping dtel-md-ingress-timestamp {
    description
      "Detailed semantics of ingress timestamp in INT metadata and
       telemetry report metadata";

    uses dtel-md-semantics-time-units;
  }

  grouping dtel-md-egress-timestamp {
    description
      "Detailed semantics of egress timestamp in INT metadata and
       telemetry report metadata";

    uses dtel-md-semantics-time-units;
  }

  grouping dtel-md-egress-port-tx-utilization {
    description
      "Detailed semantics of egress port tx utilization INT metadata
       and telemetry report metadata";

    uses dtel-md-semantics-utilization-units;

    // TBD: Need to specify something about computation
    // Moving average?
    // Time frame?
  }

  grouping dtel-md-drop-reason {
    description
      "Detailed semantics of drop reason in telemetry report
       metadata";

    leaf drop-reason-reference {
      type oc-inet:url;
      description
        "A reference to a URL where the drop reasons are defined";
    }
  }

  grouping dtel-md-int-last-hop-md-report {
    description
      "Properties of INT last hop telemetry reports generated by
       this node";

    leaf int-last-hop-md-report {
      type int-last-hop-md-report-position;
      description
        "Specifies whether last hop metadata is included in the same
         telemetry report as the embedded INT metadata from previous
         hops, and whether the last hop metadata is included in
         embedded INT metadata or in the Telemetry Report header";
    }
  }

  grouping dtel-md-semantics-identifiers {
    description
      "Identifiers used in dataplane telemetry metadata";

    container switch-id {
      description
        "Container for switch_id";

      container config {
        description
          "switch_id config";
        uses dtel-md-switch-id;
      }

      container state {
        config false;
        description
          "State information for switch_id";
        uses dtel-md-switch-id;
      }
    }

    // TBD: Add anything related to port IDs?

  }

  grouping dtel-md-semantics-details {
    description
      "Detailed semantics of dataplane telemetry metadata";

    container hop-latency {
      description
        "Container for hop latency";

      container config {
        description
          "Hop latency config";
        uses dtel-md-hop-latency;
      }

      container state {
        config false;
        description
          "State information for hop latency";
        uses dtel-md-hop-latency;
        uses dtel-md-metadata-supported;
      }
    }

    container queue-occupancy {
      description
        "Container for queue occupancy";

      container config {
        description
          "Queue occupancy config";
        uses dtel-md-queue-occupancy;
      }

      container state {
        config false;
        description
          "State information for queue occupancy";
        uses dtel-md-queue-occupancy;
        uses dtel-md-metadata-supported;
      }
    }

    container ingress-timestamp {
      description
        "Container for ingress timestamp";

      container config {
        description
          "Ingress timestamp config";
        uses dtel-md-ingress-timestamp;
      }

      container state {
        config false;
        description
          "State information for ingress timestamp";
        uses dtel-md-ingress-timestamp;
        uses dtel-md-metadata-supported;
      }
    }

    container egress-timestamp {
      description
        "Container for egress timestamp";

      container config {
        description
          "Egress timestamp config";
        uses dtel-md-egress-timestamp;
      }

      container state {
        config false;
        description
          "State information for egress timestamp";
        uses dtel-md-egress-timestamp;
        uses dtel-md-metadata-supported;
      }
    }

    container egress-port-tx-utilization {
      description
        "Container for egress port tx utilization";

      container config {
        description
          "Egress port tx utilization config";
        uses dtel-md-egress-port-tx-utilization;
      }

      container state {
        config false;
        description
          "State information for egress port tx utilization";
        uses dtel-md-egress-port-tx-utilization;
        uses dtel-md-metadata-supported;
      }
    }

    container drop-reason {
      description
        "Container for drop reason";

      container config {
        description
          "Drop reason config";
        uses dtel-md-drop-reason;
      }

      container state {
        config false;
        description
          "State information for drop reason";
        uses dtel-md-drop-reason;
        uses dtel-md-metadata-supported;
      }
    }
  }

  grouping dtel-md-semantics-report-properties {
    description
      "Properties of telemetry reports generated by this node";

    container int-last-hop-md-report {
      description
        "Container for INT last hop telemetry report properties";

      container config {
        description
          "INT last hop telemetry report config";
        uses dtel-md-int-last-hop-md-report;
      }

      container state {
        description
          "State information for INT last hop telemetry reports";
        uses dtel-md-int-last-hop-md-report;
      }
    }
  }

  grouping dtel-md-semantics-top {
    description
      "Top level grouping for dataplane telemetry metadata semantics";

    container identifiers {
      description
        "Identifiers used in dataplane telemetry metadata";
      uses dtel-md-semantics-identifiers;
    }

    container md-semantics {
      description
        "Semantics of dataplane telemetry metadata";
      uses dtel-md-semantics-details;
    }

    container report-properties {
      description
        "Properties of telemetry reports generated by this node";
      uses dtel-md-semantics-report-properties;
    }
  }

  // data definition statements
  uses dtel-md-semantics-top;

}
